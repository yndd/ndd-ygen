module srl_nokia-boot {
  yang-version 1.1;
  namespace "urn:srl_nokia/boot";
  prefix srl-boot;

  import srl_nokia-system {
    prefix srl-system;
  }
  import srl_nokia-common {
    prefix srl-comm;
  }
  import srl_nokia-interfaces {
    prefix srl-if;
  }

  description
    "This module defines configuration and operational state data related to the booting the system.";

  revision 2020-12-31 {
    description
      "SRLinux 20.12.1";
  }
  revision 2020-06-30 {
    description
      "SRLinux 20.6.1";
  }
  revision 2019-11-30 {
    description
      "SRLinux 19.11.1";
  }

  typedef client-id {
  	type enumeration {
  	  enum serial {
  		description
  		 "Use the chassis serial number as the client ID";
  	  }
      // Type mac is not used until dhcp-client-mgr get cli nobe to select
  	  // enum mac {
  	  //  description
  	  //	 "Use the chassis MAC address as the client ID";
  	  // }
  	}
  }

  grouping boot-images-top {
	  leaf-list image {
	    type srl-comm:local-file-no-path;
	    max-elements 3;
	    ordered-by user;
		config false;
	    description
	      "Ordered list of local images used to boot the system

	      This directly translates into boot configuration in grub, where the images are tried in the order specified by the user. Images are sourced via the internal SD card, and the value passed is the folder that contains the initramfs, kernel, and squashfs image. The search path for these directories is /mnt/nokiaos/<folder>";
	  }
  }

  grouping boot-autoboot-top {
  	container autoboot {
  	  description
  	   "Top-level container for configuration and state data related to autobooting the system";
  	  leaf admin-state {
  	  	type srl-comm:admin-state;
  	  	//default "enable";
  	  	description
  	  	  "Administratively enable or disable autoboot functionality";
  	  }
  	  leaf oper-state {
  	  	type string;
  	  	config false;
  	  	description
  	  	  "The current operational status of the autoboot process";
  	  }
  	  leaf timeout {
  	  	type uint32 {
                range "200 .. 3600";
            }
  	  	units "seconds";
  	  	//default 3600;
  	  	description
  	  	  "Sets the timeout for each attempt to autoboot";
  	  }
  	  leaf attempts {
  	  	type uint8 {
                range "1 .. 10";
            }
  	  	//default 3;
  	  	description
  	  	  "Sets the amount of executions to try autoboot, before rebooting the system";
  	  }
  	  leaf interface {
  	  	type leafref {
  	  		path "/srl-if:interface/srl-if:name";
  	  	}
  	  	default "mgmt0";
  	  	description
  	  	  "Sets the interface to use for autoboot functionality";
  	  }
  	  leaf client-id {
  	  	type client-id;
  	  	//default "serial";
  	  	description
  	  	 "The client ID to use on outgoing DHCP requests";
  	  }
  	}
  }

  grouping boot-top {
    container boot {
      description
        "Top-level container for configuration and state data related to booting the system";
      uses boot-images-top;
      uses boot-autoboot-top;
    }
  }

  augment "/srl-system:system" {
    uses boot-top;
  }
}
