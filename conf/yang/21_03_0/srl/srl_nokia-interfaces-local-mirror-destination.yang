module srl_nokia-interfaces-local-mirror-destination {
  yang-version 1.1;

  // namespace
  namespace "urn:srl_nokia/interfaces/local-mirror-destination";

  prefix "srl_nokia-if-local-mirror-dest";

  // import some basic types
  import srl_nokia-interfaces { prefix srl_nokia-if; }
  import srl_nokia-common { prefix srl_nokia-comm; }

  description
    "Model for managing subinterfaces of type local-mirror-destination";

  revision 2021-02-02 {
    description
      "SRLinux 21.6.1";
  }

  grouping subinterface-local-mirror-destination-top {
    container local-mirror-destination {
      presence "Performs local-mirror-destination";
      description
        "Container for options related to local mirror destination";
      must "not(starts-with(../srl_nokia-if:name, 'mgmt') or starts-with(../srl_nokia-if:name, 'lo') or starts-with(../srl_nokia-if:name, 'system') or starts-with(../srl_nokia-if:name, 'irb'))" {
        error-message "local mirror destination is not supported on mgmt, lo, system, or irb interfaces";
      }
      must "(../../srl_nokia-if:subinterface/srl_nokia-if:type = 'local-mirror-dest')" {
        error-message "local-mirror-destination is only allowed on subinterfaces with type local-mirror-dest";
      }
      leaf admin-state {
        type srl_nokia-comm:admin-state;
        default "enable";
        description "The configurable state of the local mirror destination"; // possible values are enable or disable
      }
      leaf oper-state {
        config false;
        type srl_nokia-comm:oper-state;
        description "The operational state of the local mirror destination"; // possible values are up or down
      }
      container statistics {
        config false;
        leaf mirrored-packets-forwarded {
          type srl_nokia-comm:zero-based-counter64;
          description
            "Total forwarded mirrored packets";
        }
        leaf mirrored-packets-dropped {
          type srl_nokia-comm:zero-based-counter64;
          description
            "Total dropped mirrored packets";
        }
      }
    }
  }
 
  augment "/srl_nokia-if:interface/srl_nokia-if:subinterface" {
    uses subinterface-local-mirror-destination-top;
  }
 
}
