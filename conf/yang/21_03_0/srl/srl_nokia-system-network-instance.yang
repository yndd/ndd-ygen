module srl_nokia-system-network-instance {

  yang-version 1.1;

  namespace "urn:srl_nokia/system-network-instance";
  prefix "srl_nokia-system-netinst";

  import srl_nokia-common {
      prefix srl_nokia-comm;
  }
  import srl_nokia-bgp-vpn {
      prefix srl_nokia-bgp-vpn;
  }
  import srl_nokia-rib-bgp {
      prefix srl_nokia-rib-bgp-routes;
  }
  import srl_nokia-interfaces {
    prefix srl_nokia-if;
  }
  import srl_nokia-extensions {
    prefix srl_nokia-ext;
  }
  import srl_nokia-features {
    prefix srl_nokia-feat;
  }
  import srl_nokia-system {
    prefix srl_nokia-system;
  }

  description
    "This yang file models configuration and state of the system network-instance.";

  revision 2020-10-30 {
      description
        "SRLinux 20.10.1";
  }

  grouping system-network-instance-top {
    description
      "Top-level grouping containing the system network-instance configuration and state.";
    container network-instance {
      //srl_nokia-ext:first-released "20.10.1";
      presence "Configure the system network-instance.";
      container protocols {
        description
          "The routing protocols that are enabled for this
           network-instance.";
        //uses srl_nokia-bgp-vpn:bgp-vpn-top;
        container evpn {
          if-feature "srl_nokia-feat:evpn";
          presence "System network-instance evpn configuration and state.";
        }
      }
    }
  }
  augment "/srl_nokia-system:system" {
    uses system-network-instance-top;
  }
}
