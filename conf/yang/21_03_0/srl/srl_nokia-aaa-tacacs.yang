module srl_nokia-aaa-tacacs {
  yang-version 1.1;
  // namespace
  namespace "urn:srl_nokia/aaa-tacacs";
  prefix srl-aaa-tacacs;

  import srl_nokia-aaa-types {
    prefix srl-aaa-types;
  }
  import srl_nokia-system {
    prefix srl-system;
  }
  import srl_nokia-common {
    prefix srl-comm;
  }
  import srl_nokia-extensions {
    prefix srl-ext;
  }

  description
    "This module defines configuration and operational state data
     related to the TACACS+ protocol for authentication,
     authorization, and accounting.";

  // extension statements
  // feature statements
  // identity statements
  // typedef statements

  revision 2019-11-30 {
    description
      "SRLinux 19.11.1";
  }

  // grouping statements

  grouping aaa-tacacs-server-config {
    description
      "Configuration data for a TACACS+ server";
    leaf port {
      type srl-comm:port-number;
      default "49";
      must '../../../type = "srl-aaa-types:tacacs"' {
        error-message "TACACS+ port configuration supported for 'tacacs' server type only";
      }
      description
        "The port number on which to contact the TACACS+ server";
    }
    leaf secret-key {
      type srl-comm:routing-password;
      must '../../../type = "srl-aaa-types:tacacs"' {
        error-message "TACACS+ secret-key configuration supported for 'tacacs' server type only";
      }
      description
        "The unencrypted shared key used between the system and server";
    }
    // leaf source-address {
    //     type srl-comm:ip-address;
    //     description "Source IP address to use in messages to the TACACS server";
    // }
  }

  grouping aaa-tacacs-server-top {
    description
      "Top-level grouping for TACACS+ server data";
    container tacacs {
      description
        "Top-level container for TACACS+ server data";
      uses aaa-tacacs-server-config;
    }
  }
}
