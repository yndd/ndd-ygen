module srl_nokia-snmp {
    yang-version 1.1;

    // namespace
    namespace "urn:srl_nokia/snmp";
    prefix "srl_nokia-snmp";
	
    import srl_nokia-system {
    	prefix srl-system;
    }   
    import srl_nokia-network-instance {
        prefix srl-netinst;
    }
    import srl_nokia-common {
        prefix srl-comm;
    }
    import srl_nokia-extensions {
      prefix srl-ext;
    }

    description "This module defines SNMP configuration and state";

  revision 2020-06-30 {
    description
      "SRLinux 20.6.1";
  }
  revision 2019-11-30 {
    description
      "SRLinux 19.11.1";
  }

    typedef snmp-version {
        type enumeration {
            enum v2c {
                description
                    "Version v2c of SNMP";
            }
        }
        description
            "Version of SNMP for the SNMP server to use";
    }

    typedef community-permission {
        type enumeration {
            enum r {
                description
                    "Permit read only access for this community";
            }
        }
        description
            "Permission to apply to this community";
    }

    grouping community-entry {
        leaf name {
	    description
	        "Name of the SNMP community";
            type srl-comm:name {
                srl-ext:generated-class-name "SecretKey";
            }
        }
        leaf permission {
	    description
	      "Permissions to allocate to this community";
            type community-permission;
            default "r";
        }
        leaf version {
	    description
	      "SNMP version to use with this community";
            type snmp-version;
            default "v2c";
        }
    }

    grouping community-interface {
        description "List of communities used in the system";
        list community {
	    description
	      "List of configured SNMP communities";
            key name;
            uses community-entry;
        }
    }

    grouping community-interface-nolist {
        description "Grouping for single community support";
	leaf community {
            type srl-comm:name {
                srl-ext:generated-class-name "SecretKey";
            }
	}
    }

    grouping network-instance-entry-config {
        leaf admin-state {
            type srl-comm:admin-state;
            description 
                "Enables the SNMP server in this network-instance";
        }
        leaf-list source-address {
            type srl-comm:ip-address;
            description
                "List of IP addresses for the SNMP server to listen on within the network-instance";
        }
        /*leaf-list trace-options {
	    description
	      "List of enabled trace-options";
            type identityref {
            	base srl-snmp-trace:snmp-trace-option;
            }
        }*/
    }

    grouping network-instance-entry-state {
        leaf oper-state {
            type srl-comm:oper-state;
            config false;
            description 
                "Details the operational state of the SNMP server";
        }
    }

    grouping network-instance-entry {
        leaf name {
          type leafref {
            path "/srl-netinst:network-instance/srl-netinst:name";
          }
          must 'not(/srl-netinst:network-instance[srl-netinst:name=current()]/srl-netinst:type = "srl-netinst:mac-vrf")' {
            error-message "SNMP server cannot be started in a network-instance of type 'mac-vrf'";
          }
          description
            "Reference to a configured network-instance";
        }
        uses network-instance-entry-config;
        uses network-instance-entry-state;
    }

     grouping network-instance-interface {
        list network-instance {
	    description
	      "List of network-instances to run an SNMP server in";
            key name;
            uses network-instance-entry;
        }
    }

    grouping snmp-top {
        container snmp {
	    description
	        "Top-level container for SNMP configuration and state";
            uses community-interface-nolist;
            uses network-instance-interface;
        }
    }
    
    augment "/srl-system:system" {
        uses snmp-top;
  }
}
