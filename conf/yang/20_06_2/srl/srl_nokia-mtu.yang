module srl_nokia-mtu {
  yang-version 1.1;
  namespace "urn:srl_nokia/mtu";
  prefix srl-mtu;

  import srl_nokia-features {
    prefix srl_nokia-feat;
  }

  import srl_nokia-system {
    prefix srl_nokia-system;
  }

  description
    "This module defines configuration and operational state data related to the system MTU";

  revision 2020-06-30 {
    description
      "SRLinux 20.6.1";
  }
  revision 2019-11-30 {
    description
      "SRLinux 19.11.1";
  }

  grouping mtu-config-top {
    description
      "Configuration data related to the system MTU";
    leaf default-port-mtu {
      type uint16 {
        range "1500..9500";
      }
      default "9232";
      description
        "System default port MTU in bytes including ethernet overhead but excluding 4-bytes FCS

        The 7220 IXR-D1, 7220 IXR-D2 and 7220 IXR-D3 systems support a maximum port MTU of 9412 bytes.";
    }
    leaf default-l2-mtu {
      if-feature srl_nokia-feat:bridged;
      type uint16 {
        range "1500..9500";
      }
      default "9232";
      description
        "System default Layer-2 MTU in bytes including ethernet overhead and VLAN tags but excluding 4-bytes FCS

        The 7220 IXR-D1, 7220 IXR-D2 and 7220 IXR-D3 systems support a maximum L2 MTU of 9412 bytes.";
    }
    leaf default-ip-mtu {
      type uint16 {
        range "1280..9486";
      }
      default "1500";
      description
        "System default IP MTU in bytes including the IP header but excluding Ethernet overhead

        The 7220 IXR-D1, 7220 IXR-D2 and 7220 IXR-D3 systems support a maximum IP MTU of 9398 bytes.";
    }
    leaf min-path-mtu {
      type uint16 {
        range "552..9232";
      }
      default 552;
      description
        "Sets the minimum path MTU to use when receiving an ICMP fragmentation needed message

        This is controlled via the kernel min_pmtu option. In the event an ICMP fragmentation needed message is received by the kernel, the system will drop the session to this MTU to allow packets to traverse the entire path.";
    }
  }

  grouping mtu-top {
    container mtu {
      description
        "Top-level container for configuration and state data related to the system MTU";
      uses mtu-config-top;
    }
  }

  augment "/srl_nokia-system:system" {
    uses mtu-top;
  }
}
