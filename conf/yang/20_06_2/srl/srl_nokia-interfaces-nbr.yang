module srl_nokia-interfaces-nbr {
  yang-version 1.1;

  // namespace
  namespace "urn:srl_nokia/interfaces/ip/nbr";

  prefix "srl_nokia-if-ip-nbr";

  // import some basic types
  import ietf-inet-types {
    prefix inet;
  }
  import srl_nokia-interfaces {
    prefix srl_nokia-if;
  }
  import srl_nokia-if-ip {
    prefix srl_nokia-if-ip;
  }
  import srl_nokia-common {
    prefix srl_nokia-comm;
  }
  import srl_nokia-extensions {
    prefix srl_nokia-ext;
  }
  import ietf-yang-types {
    prefix yang;
  }

  description
    "Model for managing ARP and IPv6 neighbor discovery on IP subinterfaces.";

  revision 2020-06-30 {
    description
      "SRLinux 20.6.1";
  }
  revision 2019-11-30 {
    description
      "SRLinux 19.11.1";
  }

  typedef neighbor-origin {
    type enumeration {
      enum other {
        value 1;
      }
      enum static {
        value 2;
      }
      enum dynamic {
        value 3;
      }
    }
    description
      "The origin of the neighbor entry.";
    // see RFC 7277.
  }

  grouping ipv4-nbr-top {
    container arp {
      leaf timeout {
        type uint16 {
            range "60..65535";
        }
        units seconds;
        default 14400;
        description
          "Duration of time that dynamic ARP entries remain in the ARP cache before they expire

          A change to this value does not affect existing entries until they are refreshed.";
      }
      list neighbor {
        srl_nokia-ext:show-importance high;
        key "ipv4-address";
        description
          "List of static and dynamic ARP cache entries that map an IPv4 address to a MAC address

          To configure a static ARP entry a value must be written into this leaf and the link-layer-address leaf.";
        reference
          "RFC 826: An Ethernet Address Resolution Protocol";

        leaf ipv4-address {
          type srl_nokia-comm:ipv4-address;
          description "IPv4 address resolved by the ARP entry

          To configure a static neighbor entry a value must be written into this leaf and the link-layer-address leaf.";
        }

        leaf link-layer-address {
          type srl_nokia-comm:mac-address;
          mandatory "true";
          description
            "The resolving MAC address of the ARP entry

            To configure a static ARP entry a value must be written into this leaf and the ipv4-address leaf.";
        }

        leaf origin {
          config false;
          type neighbor-origin;
          description
            "The origin of the ARP entry";
            // Refer to RFC 7277.
        }

        leaf expiration-time {
          config false;
          type srl_nokia-comm:date-and-time-delta;
          description
            "The date and time when the dynamic ARP entry is set to expire";
        }
      }
    }
  }

  augment "/srl_nokia-if:interface/srl_nokia-if:subinterface/srl_nokia-if:ipv4" {
    description
      "IPv4 addr family configuration for interfaces";

    uses ipv4-nbr-top;
  }

  grouping ipv6-nbr-top {
    container neighbor-discovery {
      leaf duplicate-address-detection {
        type boolean;
        default true;
        description
          "Enables Duplicate Addres Detection on all tentative addresses

          This applies to link-local and global unicast addresses. Only one transmission is done; there are no retransmissions.

          Must be true on an IPv6 subinterface that has dhcp-client enabled.";
      }
      leaf reachable-time {
        type uint32 {
            range "30..3600";
        }
        units seconds;
        default 30;
        description
         "The period of time that a dynamic IPv6 neighbor cache entry is considered reachable after a reachability confirmation event

         After this time expires the neighbor state moves to STALE.";
      }
      leaf stale-time {
        type uint32 {
            range "60..65535";
        }
        units seconds;
        default 14400;
        description
          "The maximum time that a dynamic IPv6 neighbor cache entry can remain in the STALE state before it is removed

          This limit is reached only if no traffic is sent/queued towards the neighbor during the entire duration of the timer.";
      }
      list neighbor {
        srl_nokia-ext:show-importance high;
        key "ipv6-address";
        description
          "List of static and dynamic ND cache entries that map an IPv6 address to a MAC address";
        reference
          "RFC 4861: Neighbor Discovery for IP version 6 (IPv6)";

        leaf ipv6-address {
          type srl_nokia-comm:ipv6-address;
          description
            "IPv6 address resolved by the ND cache entry

            To configure a static neighbor entry a value must be written into this leaf and the link-layer-address leaf.";
        }

        leaf link-layer-address {
          type srl_nokia-comm:mac-address;
          mandatory "true";
          description
            "The resolving MAC address of the ND cache entry

            To configure a static neighbor entry a value must be written into this leaf and the ipv6-address leaf.";
        }

        leaf origin {
          config false;
          type neighbor-origin;
          description
            "The origin of the neighbor cache entry.";
            // Refer to RFC 7277.
        }

        leaf is-router {
          config false;
          type boolean;
          description
            "Indicates that the neighbor node claims to be a router (R bit in the Neighbor Advertisement message)";
          // Refer to RFC 7277.
        }

        leaf current-state {
          config false;
          description
            "The Neighbor Unreachability Detection state";
          type enumeration {
            enum incomplete { value 0; }
            enum reachable  { value 1; }
            enum stale      { value 2; }
            enum delay      { value 3; }
            enum probe      { value 4; }
          }
        }

        leaf next-state-time {
            config false;
            type srl_nokia-comm:date-and-time-delta;
            description
              "The date and time when the neighbor state is expected to transition to the next state";
        }
      }
    }
  }

  augment "/srl_nokia-if:interface/srl_nokia-if:subinterface/srl_nokia-if:ipv6" {
    description
      "IPv6 address family configuration for interfaces";

    uses ipv6-nbr-top;
  }
}
