module srl_nokia-maintenance-mode {
  yang-version 1.1;

  // namespace

  namespace "urn:srl_nokia/maintenance-mode";
  prefix srl-m-mode;

  import srl_nokia-system {
    prefix srl-system;
  }
  import srl_nokia-network-instance {
    prefix srl-netinst;
  }
  import srl_nokia-bgp {
    prefix srl-bgp;
  }

  // import some basic types

  import srl_nokia-common {
    prefix srl_nokia-comm;
  }
  import srl_nokia-routing-policy {
    prefix srl-rpol;
  }

  description
    "This module defines configuration and operational state data for Maintenance Mode.";

  revision 2020-06-30 {
    description
      "SRLinux 20.6.1";
  }
  revision 2019-11-30 {
    description
      "SRLinux 19.11.1";
  }

  grouping group-members-top {
    container members {
      description
        "Container for specifying the members of the maintenance group - i.e. the components that will eventually be taken out of service for repair or replacement.";
      container bgp {
        description
          "Container for specifying the BGP members of the maintenance group";
        list network-instance {
          description
              "List of network instances with one or more peers to be placed in maintenance mode";

          key name;
          leaf name {
            type leafref {
              path "/srl-netinst:network-instance/srl-netinst:name";
            }
            description
              "A unique name identifying the network instance";
          }
          leaf-list peer-group {
            description
              "List of BGP peer groups that belong to the network instance and that should be part of the maintenance group

              If this list is empty and so is the neighbor list, then the system interprets the meaning as ALL static and dynamic sessions belonging to the specified network-instance.";
            type leafref {
              path "/srl-netinst:network-instance/srl-netinst:protocols/srl-bgp:bgp/srl-bgp:group/srl-bgp:group-name";
            }
          }
          leaf-list neighbor {
            description
              "List of BGP neighbors that belong to the network instance and that should be part of the maintenance group

              It is not necessary to list neighbors that are members of peer-groups that are already listed.

              If this list is empty and so is the group list, then the system interprets the meaning as ALL static and dynamic sessions belonging to the specified network-instance.";
            type leafref {
              path "/srl-netinst:network-instance/srl-netinst:protocols/srl-bgp:bgp/srl-bgp:neighbor/srl-bgp:peer-address";
            }
          }
        }
      }
    }
  }

  grouping group-top {
    description
      "Top-level grouping for Maintenance Mode Group";
    list group {
      description
        "List of user-configured and built-in maintenance groups";
      key "name";
      leaf name {
        type string;
        description
          "Name of the maintenance group. 
           The name \"system\" is reserved";
      }
      container maintenance-mode {
        description
          "Container with options for activating and deactivating maintenance mode for this group";
        leaf admin-state {
          type srl_nokia-comm:admin-state;
          default "disable";
          description
            "Enable or disable maintenance mode for this group

            The enable setting is blocked if there is another maintenance group with at least one BGP session in its scope that overlaps with this maintenance group and that other maintenance group is currently in maintenance mode.

            While a maintenance group is in maintenance mode it is not possible to modify the BGP configuration of its members.";
        }
      }
      leaf maintenance-profile {
        description
          "Leaf reference to /system/maintenance/profile/name";
        type leafref {
          path "/srl-system:system/srl-m-mode:maintenance/srl-m-mode:profile/name";
        }
      }
      uses group-members-top;
    }
    // list group
  }

  grouping profile-top {
    description
      "List of user-configured maintenance profiles";
    list profile {
      key "name";
      leaf name {
        type string;
        description
          "Name of the maintenance profile";
      }
      container bgp {
        description
          "Container for BGP policies used to achieve traffic draining";
        leaf import-policy {
          description
            "A reference to the pre-configured routing policy to apply as an additional/final import policy on BGP sessions in the maintenance group";
          type leafref {
            path "/srl-rpol:routing-policy/srl-rpol:policy/srl-rpol:name";
          }
        }
        leaf export-policy {
          description
            "A reference to the pre-configured routing policy to apply as an additional/final export policy on BGP sessions in the maintenance group";
          type leafref {
            path "/srl-rpol:routing-policy/srl-rpol:policy/srl-rpol:name";
          }
        }
       }
     } // list profile
   } // profile-top

   grouping maintenance-top {
     description
       "Top-level grouping for Maintenance mode";
     container maintenance {
       presence "Configure Maintenance Mode";
       description
         "Top-level container for Maintenance Mode configuration";
       uses group-top;
       uses profile-top;
      }
    }

    augment "/srl-system:system" {
        uses maintenance-top;
    }
}
