module srl_nokia-platform-ip-mpls-fwd-resources {
  yang-version 1.1;
  namespace "urn:srl_nokia/platform-ip-mpls-fwd-resources";
  prefix srl_nokia-platform-ip-mpls-fwd-resources;

  import srl_nokia-common { prefix srl_nokia-comm; }
  import srl_nokia-platform {prefix srl_nokia-platform; }
  import srl_nokia-platform-lc {prefix srl_nokia-platform-lc; }
  import srl_nokia-platform-resource-monitoring {prefix srl_nokia-platform-res-mon; }
  import srl_nokia-features { prefix srl_nokia-feat; }

  description
    "This module defines configuration and operational state related to IP and MPLS forwarding resources in the system";

  revision 2020-06-30 {
    description
      "SRLinux 20.6.1";
  }
  revision 2019-11-30 {
    description
      "SRLinux 19.11.1";
  }

  identity ip-mpls-forwarding-resources {
    description
      "Base type for routing resources";
  }

  identity ip-fib {
    if-feature srl_nokia-feat:jericho2;
    base ip-mpls-forwarding-resources;
    description
      "One of these resources is used by every host and non-host route to an IPv4 or IPv6 destination. Free entries represents the maximum number of IPv4 hosts that can still be added or the maximum number of IPv4 LPM routes that can be added, whichever is less.";
  }

  identity ip-arp-nd {
    base ip-mpls-forwarding-resources;
    description
      "One of these resources is used for every IPv4 ARP or IPv6 neighbor entry. Free entries represents the maximum number of IPv4 ARP entries or IPv6 neighbor entries that can still be added.";
  }

  identity direct-next-hops {
    base ip-mpls-forwarding-resources;
    description
      "Each direct next-hop in a next-hop-group (static or dynamic) uses one of these resources. A direct next-hop is resolved by a local interface route. The same direct next-hop in two different NHGs still counts as one direct next-hop.";
  }

  identity indirect-next-hops {
    base ip-mpls-forwarding-resources;
    description
      "Each indirect next-hop in a next-hop-group (static or dynamic) uses one of these resources. An indirect next-hop is resolved by any route other than a local interface route. The same indirect next-hop in two different NHGs still counts as one indirect next-hop.";
  }

  identity hardware-ecmp-fecs {
    if-feature srl_nokia-feat:jericho2;
    base ip-mpls-forwarding-resources;
    description
      "This represents the pool of resources used to support ECMP forwarding in hardware. On a J2 IMM the utilization for this pool of resources is calculated as the maximum utilization of the following tables: L1 ECMP FECs, L2 ECMP FECs, L1 ECMP member FECs and L2 ECMP member FECs";
  }

  identity hardware-fecs {
    if-feature srl_nokia-feat:jericho2;
    base ip-mpls-forwarding-resources;
    description
      "This represents the pool of resources used to support non-ECMP forwarding in hardware. On a J2 IMM the utilization for this pool of resources is calculated as the maximum utilization of the following tables: L1 non-ECMP FECs, L2 non-ECMP FECs.";
  }

  identity asic-forwarding-resource {
    description
      "Base type for datapath forwarding resources that are ASIC-specific";
  }

  identity egress-next-hops {
    base asic-forwarding-resource;
    description
      "One of these resources is used for every (ECMP or non-ECMP) IP next-hop, IPv4 ARP entry and IPv6 neighbor entry.";
  }

  identity ip-lpm-routes {
    base asic-forwarding-resource;
    description
      "Represents the resources used to store IPv4 and IPv6 routes for longest-prefix-match (LPM) lookup.
      
      The used number represents the number of half-wide entries in the L3_DEFIP table. An IPv4 route requires a half-wide entry. An IPv6 route that is /64 or less requires a single-wide entry. An IPv6 route that is more than /64 requires a double-wide entry. Free entries is the remaining number of half-wide entries, and therefore represents the number of IPv4 routes that can still be added; the number of IPv6 routes that can still be added will be less.";
  }

  identity ip-hosts {
    base asic-forwarding-resource;
    description
      "Represents the resources used to store IPv4 and IPv6 host routes.
      
      The used number represents the number of single-wide entries in the dedicated plus shared IP-host UFT banks that are already used. A single-wide entry is used for an IPv4 host route. A double-wide entry is used for an IPv6 host route. Free entries is the remaining number of single-wide entries, and therefore represents the number of IPv4 host routes that can still be added; the number of IPv6 host routes that can still be added will be less.";
  }

  identity ecmp-groups {
    base asic-forwarding-resource;
    description
      "One of these resources is used for every ECMP group (overlay or underlay) programmed into the datapath.";
  }

  identity ecmp-members {
    base asic-forwarding-resource;
    description
      "One of these resources is used for every ECMP next-hop programmed into the datapath.";
  }

  grouping ip-mpls-forwarding-resource-monitoring {
    container ip-mpls-forwarding {
      list resource {
        key name;
        leaf name {
          type identityref  {
            base ip-mpls-forwarding-resources;
          }
          description
            "The name of the IP-MPLS forwarding resource";
        }
        leaf rising-threshold-log {
          type srl_nokia-comm:percentage;
          default "90";
          description
            "Sets the threshold that triggers the generation of a WARNING log whenever the utilization of the IP-MPLS forwarding resource in any linecard/complex/core reaches this value in a rising direction";
        }
        leaf falling-threshold-log {
          type srl_nokia-comm:percentage;
          default "70";
          description
            "Sets the threshold that triggers the generation of a NOTICE log whenever the utilization of the IP-MPLS forwarding resource in any linecard/complex/core reaches this value in a falling direction";
        }
      }
      container asic {
        if-feature srl_nokia-feat:trident3;
        description
          "Container for monitoring ASIC-specific forwarding resources";
        list resource {
          key name;
          leaf name {
            type identityref  {
              base asic-forwarding-resource;
            }
            description
              "The name of the ASIC-specific forwarding resource";
          }
          leaf rising-threshold-log {
            type srl_nokia-comm:percentage;
            default "90";
            description
              "Sets the threshold that triggers the generation of a WARNING log whenever the utilization of the forwarding resource reaches this value in a rising direction";
          }
          leaf falling-threshold-log {
            type srl_nokia-comm:percentage;
            default "70";
            description
              "Sets the threshold that triggers the generation of a NOTICE log whenever the utilization of the forwarding resource reaches this value in a falling direction";
          }
        }
      } 
    }
  }

  grouping ip-mpls-forwarding-utilization {
    container ip-mpls-forwarding {
      config false;
      list resource {
        key name;
        leaf name {
          type identityref  {
            base ip-mpls-forwarding-resources;
          }
          description
            "The name of the IP-MPLS forwarding resource";
        }
        leaf used {
          type srl_nokia-comm:percentage;
          description
            "The percentage of the resource that is currently used";
        }
      }
      container asic {
        if-feature srl_nokia-feat:trident3;
        description
          "Container for monitoring ASIC-specific datapath resources";
        list resource {
          key name;
          leaf name {
            type identityref  {
              base asic-forwarding-resource;
            }
            description
              "The name of the ASIC-specific datapath resource";
          }
          leaf used {
            type uint32;
            description
              "The number of used entries";
          }
          leaf free {
            type uint32;
            description
              "The number of free (remaining) entries";
          }
        }
      }
    }
  }

  augment "/srl_nokia-platform:platform/srl_nokia-platform-res-mon:resource-monitoring" {
    uses ip-mpls-forwarding-resource-monitoring;
  }

  augment "/srl_nokia-platform:platform/srl_nokia-platform-lc:linecard/srl_nokia-platform-lc:forwarding-complex" {
    uses ip-mpls-forwarding-utilization;
  }
}
