module srl_nokia-aft {
  yang-version 1;

  // namespace

  namespace "urn:srl_nokia/aft";
  prefix srl_nokia-aft;

  import ietf-inet-types {
    prefix inet;
  }
  import srl_nokia-common {
    prefix srl_nokia-comm;
  }
  import srl_nokia-network-instance {
    prefix srl_nokia-netinst;
  }
  import srl_nokia-extensions {
    prefix srl_nokia-ext;
  }

  description
    "A model describing the forwarding entries installed on a network
     element. It should be noted that this model is not expected to
     align 1:1 with the underlying structure used directly by a
     forwarding element (e.g., linecard), but rather provide an
     abstraction that can be consumed by an NMS to observe, and in some
     cases manipulate, the internal forwarding database in a simplified
     manner. Since the underlying model of the forwarding table is not
     expected to align with this model, the structure described herein
     is referred to as an Abstract Forwarding Table (AFT), rather than
     the FIB.";

  revision 2018-05-23 {
    description
      "SRLinux 19.11.1";
  }

  identity install_protocol_type {
    description
      "Base type for protocols which can install prefixes into the
       RIB";
  }

  identity bgp {
    base install_protocol_type;
    description
      "BGP";
    reference "RFC 4271";
  }

  identity isis {
    base install_protocol_type;
    description
      "IS-IS";
    reference "ISO/IEC 10589";
  }

  identity ospf {
    base install_protocol_type;
    description
      "OSPFv2";
    reference "RFC 2328";
  }

  identity ospf3 {
    base install_protocol_type;
    description
      "OSPFv3";
    reference "RFC 5340";
  }

  identity static {
    base install_protocol_type;
    description
      "Locally-installed static route";
  }

  identity directly_connected {
    base install_protocol_type;
    description
      "A directly connected route";
  }

  identity local {
    base install_protocol_type;
    description
      "A local route";
  }

  identity local_aggregate {
    base install_protocol_type;
    description
      "Locally defined aggregate route";
  }

  grouping aft-entry-match-state {
    description
      "Match critiera for AFT entries";
    leaf ip-prefix {
      type srl_nokia-comm:ip-prefix;
      srl_nokia-ext:show-importance "high";
      description
        "The IP prefix that the forwarding entry matches. Used for
         Layer 3 forwarding entries.";
    }
    leaf preference {
      type uint32;
      description
        "Preference of the Route.";
    }
  }

  grouping aft-entry-nexthop-config {
    description
      "Configuration parameters relating to a next-hop entry for a AFT
       entry";
    leaf index {
      type uint64;
      description
        "A unique entry for the next-hop";
    }
  }

  grouping aft-entry-nexthop-state {
    description
      "Parameters relating to a next-hop within the AFT entry";
    leaf ip-address {
      //type inet:ip-address-no-zone;
      type string;
      srl_nokia-ext:show-importance "high";
      description
        "The IP address of the next-hop system.";
    }
    leaf origin-protocol {
        type union {
            type identityref {
                base install_protocol_type;
            }
            type string;
        }
      srl_nokia-ext:show-importance "high";
      description
        "The protocol from which the AFT entry was learned.";
    }
  }

  // structural groupings

  grouping aft-proto-top {
    description
      "Top level per-protocol grouping for the AFT.";
    container entries {
      presence "State AFT";
      description
        "Enclosing container for a list of abstract forwarding table
         entries within the network instance for a particular protocol
         (e.g., IPv4, IPv6, MPLS).";
      config false;
      list entry {
        key "index";
        description
          "A forwarding database entry within the network instance";
        leaf index {
          //          type leafref {
          //            path "../config/index";
          //          }
          type uint64;
          description
            "A pointer to the index of the AFT entry within the
             network instance";
        }
        container match {
          presence "State match";
          description
            "Match criteria for the AFT entry";
          //          container config {
          //            description
          //              "Configuration of match criteria for the AFT entry";
          //          }
          container state {
            presence "State parameters";
            config false;
            description
              "Operational state parameters for match criteria of the
               AFT entry";
            uses aft-entry-match-state;
          }
          //          uses oc-if:interface-ref-state;
        }
        list next-hop {
          key "index";
          description
            "A next-hop associated with the forwarding instance. The
             entries within the next-hop list should only reflect
             next-hops that are actively used by the local system.
             That is to say inactive, backup or FRR next-hops should
             not be included within this list.";
          leaf index {
            //              type leafref {
            //                path "../config/index";
            //              }
            type uint64;
            description
              "A unique index identifying the next-hop entry for the
               AFT entry";
          }
          /*
                      container config {
                        description
                          "Configuration parameters relating to the AFT next-hop
                          entry";
          
                        uses aft-entry-nexthop-config;
                      }
           */
          container state {
            presence "State parameters";
            config false;
            description
              "Operational state parameters relating to the AFT
               next-hop entry";
            //             uses aft-entry-nexthop-config;
            uses aft-entry-nexthop-state;
          }
          //            uses oc-if:interface-ref;
        }
      }
    }
  }

  grouping aft-top {
    description
      "Top-level grouping allowing per-protocol instantiation of the
       AFT.";
    list aft {
      key "address-family";
      description
        "An individual abstract forwarding table associated with a
         an address family wtihin the network instance.
         The abstract forwarding tables (AFTs) that are associated
         with the network instance. An AFT is instantiated per-protocol
         running within the network-instance - such that one exists for
         IPv4 Unicast, IPv6 Unicast, MPLS, L2 forwarding entries, etc.
         A forwarding entry within the FIB has a set of next-hops,
         which may be a reference to an entry within another table -
         e.g., where a Layer 3 next-hop has an associated Layer 2
         forwarding entry.";
      leaf address-family {
        type string;
        description
          "Reference to the address family with which the AFT is
           associated";
      }
      /*
              container state {
                config false;
                description
                  "Operational state parameters relating to the AFT.";
                uses aft-config;
              }
       */
      uses aft-proto-top;
    }
  }

  augment "/srl_nokia-netinst:network-instance" {
    uses aft-top;
  }
}
