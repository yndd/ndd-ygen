module srl_nokia-policy-types {

  yang-version 1.1;

  namespace "urn:srl_nokia/policy-types";

  prefix "srl_nokia-pol-types";

  /* import srl_nokia-common { prefix srl_nokia-comm; } */

  description
    "This module contains general data definitions for use in routing
    policy.  It can be imported by modules that contain protocol-
    specific policy match and actions.";

  revision 2019-11-30 {
    description
      "SRLinux 19.11.1";
  }

  typedef comparison-operator-type {
    type enumeration {
      enum "eq";
      enum "ge";
      enum "le";
    }
    description "Operators used for comparison";
  }

  typedef as-path-regexp {
    type string {
      length "1..65535";
    }
    description "An AS Path regular expression used by policies";
  }

  typedef as-number {
    type uint32 {
      range "1..4294967295";
    }
    description
      "An autonomous system number";
  }

  identity bgp-well-known-community {
    description
      "Reserved communities within the standard community space
      defined by RFC1997. These communities must fall within the
      range 0x00000000 to 0xFFFFFFFF";
    reference "RFC1997";
  }

  identity no-export {
    base bgp-well-known-community;
    description
      "Do not export NLRI received carrying this community outside
      the bounds of this autonomous system, or this confederation if
      the local autonomous system is a confederation member AS. This
      community has a value of 0xFFFFFF01.";
    reference "RFC1997";
  }

  identity no-advertise {
    base bgp-well-known-community;
    description
      "All NLRI received carrying this community must not be
      advertised to other BGP peers. This community has a value of
      0xFFFFFF02.";
    reference "RFC1997";
  }

  identity no-export-subconfed {
    base bgp-well-known-community;
    description
      "All NLRI received carrying this community must not be
      advertised to external BGP peers - including over confederation
      sub-AS boundaries. This community has a value of 0xFFFFFF03.";
    reference "RFC1997";
  }

/*  identity no-peer {
    base bgp-well-known-community;
    description
      "An autonomous system receiving NLRI tagged with this community
      is advised not to readvertise the NLRI to external bi-lateral
      peer autonomous systems. An AS may also filter received NLRI
      from bilateral peer sessions when they are tagged with this
      community value";
    reference "RFC3765";
    }*/

  typedef bgp-std-community-type {
    type string {
      pattern '(6553[0-5]|655[0-2][0-9]|654[0-9]{2}|65[0-4][0-9]{2}'      +
              '|6[0-4][0-9]{3}|[1-5][0-9]{4}|[1-9][0-9]{1,3}|[0-9]):'      +
              '(6553[0-5]|655[0-2][0-9]|654[0-9]{2}|65[0-4][0-9]{2}'       +
              '|6[0-4][0-9]{3}|[1-5][0-9]{4}|[1-9][0-9]{1,3}|[0-9])';
    }
    description
      "Type definition for standard commmunity values represented as a string of the form N:M where N and M are integers between 0 and 65535";
    reference "RFC 1997 - BGP Communities Attribute";
  }

  typedef bgp-std-community-regexp-type {
    type string {
//      pattern '.*[0-9]+.*:.*[0-9*]+.*';
      pattern '.*:.*';        
    }
    description
      "Type definition for regular expressions that match standard BGP communities";
  }

  typedef bgp-std-community-well-known-type {
    type identityref {
      base bgp-well-known-community;
    }
    description
      "Type definition for well-known BGP standard community values";
    reference
      "IANA Border Gateway Protocol (BGP) Well Known Communities";
  }

  typedef bgp-large-community-type {
    type string {
      pattern '([1-9][0-9]{0,9}):([1-9][0-9]{0,9}):([1-9][0-9]{0,9})';
    }
    description
      "Type definition for large commmunity values represented as a string of the form A:B:C where A, B and C are integers between 0 and 4294967295";
    reference "RFC 8092 - BGP Large Communities Attribute";
  }

  typedef bgp-large-community-regexp-type {
    type string {
//      pattern '.*[0-9]+.*:.*[0-9*]+.*:.*[0-9*]+.*';
        pattern '.*:.*:.*';        
    }
    description
      "Type definition for regular expressions that match large BGP communities";
  }

}
