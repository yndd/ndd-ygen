module srl_nokia-rib-bgp {
    yang-version 1.1;

    // namespace
    namespace "urn:srl_nokia/bgp-rib";

    prefix "srl_nokia-rib-bgp-routes";

    import srl_nokia-common {
        prefix srl_nokia-comm;
    }
    import srl_nokia-network-instance {
        prefix srl_nokia-netinst;
    }

    description
      "This yang file models the state held by the BGP RIB databases.";

  revision 2020-06-30 {
    description
      "SRLinux 20.6.1";
  }
  revision 2019-11-30 {
    description
      "SRLinux 19.11.1";
  }

    grouping state-common-key {
        leaf prefix {
            type srl_nokia-comm:ip-prefix;
        }
        leaf neighbor {
            description
                "If the route was learned from a BGP neighbor, this is the IPv4 or IPv6 address of that neighbor.";
            type srl_nokia-comm:ip-address-with-zone;
        }
    }
    grouping state-routes-common {
        leaf last-modified {
            description
              "Time of the last modification of the route stored in the BGP RIB. For a route learned from a BGP neighbor the initial value is the same as last-updatereceived. If an import policy later changed some attribute of the route last-modified would be updated to reflect the time of this change.";
            type srl_nokia-comm:date-and-time;
        }
        leaf used-route {
            description
              "Indicates true if the route is being used for forwarding.";
            type boolean;
        }
        leaf valid-route {
            description
              "Indicates true if the route is valid.";
            type boolean;
        }
        leaf best-route {
            description
              "Set to true if the route is the BGP best path for the prefix.";
            type boolean;
        }
        leaf stale-route {
            description
              "Set to true if the route is stale due to BGP graceful restart.";
            type boolean;
        }
        leaf pending-delete {
            description
              "Set to true if the route is marked for deletion.";
            type boolean;
        }
        leaf tie-break-reason {
            description
              "Indicates the reason why a BGP route is sorted behind the next best route. The BGP best path displays a value of 'none'.";
            type enumeration {
                enum "unknown" {
                    value -1;
                }
                enum "none" {
                    value 0;
                }
                enum "origin" {
                    value 1;
                }
                enum "as-path-length" {
                    value 2;
                }
                enum "next-hop-cost" {
                    value 3;
                }
                enum "med" {
                    value 4;
                }
                enum "local-pref" {
                    value 5;
                }
                enum "aggregate" {
                    value 6;
                }
                enum "originator-id" {
                    value 7;
                }
                enum "cluster-list" {
                    value 9;
                }
                enum "aigp" {
                    value 11;
                }
                enum "rtm-pref" {
                    value 13;
                }
                enum "ebgp-route" {
                    value 17;
                }
                enum "peer-ip" {
                    value 19;
                }
                enum "invalid-route" {
                    value 24;
                }
            }
        }
        container invalid-reason {
            leaf rejected-route {
                description
                  "Indicates true if the route was rejected by an import policy.";
                type boolean;
            }
            leaf as-loop {
                description
                  "Indicates true if the BGP route has an AS path loop that exceeds the configured threshold.";
                type boolean;
            }
            leaf next-hop-unresolved {
                description
                  "Indicates true if the BGP route has a BGP next-hop that cannot be resolved to an outgoing interface.";
                type boolean;
            }
            leaf cluster-loop {
                description
                  "Indicates true if the BGP route has a cluster-list loop.";
                type boolean;
            }
        }
    }
    grouping bgp-rib-top {
        container bgp-rib {
            config false;
            description
              "Container for BGP RIB state.";
            container ipv4-unicast {
                config false;
                description
                  "Container for RIB state of IPv4-unicast routes.";
                container local-rib {
                    config false;
                    description
                      "Container for local RIB, containing all imported routes from other protocols plus the post-import-policy version of all IPv4 routes learned from all BGP neighbors.";
                    list routes {
                        config false;
                        key "prefix neighbor origin-protocol";
                        description
                          "List of IPv4 routes in the local RIB.";

                        uses state-common-key;
                        leaf origin-protocol {
                            description
                                "If the route was imported from another protocol, this is the protocol name.";
                            type enumeration {
                                enum "static" {}
                                enum "aggregate" {}
                                enum "direct" {}
                                enum "bgp" {}
                                enum "host" {}
                                enum "isis" {}
                                enum "ospfv2" {}
                                enum "ospfv3" {}
                                enum "local" {}
                                enum "sdk" {}
                            }
                        }

                        uses state-routes-common;
                        leaf attr-id {
                            description
                              "Leaf reference to networkinstance/bgp-rib/attr-sets/attr-set/index";
                            type leafref {
                                path "../../../../srl_nokia-rib-bgp-routes:attr-sets/srl_nokia-rib-bgp-routes:attr-set/srl_nokia-rib-bgp-routes:index";
                            }
                        }
                    }
                }

                container rib-in-out {
                    config false;
                    description
                      "Container for BGP routes learned and advertised to BGP neighbors.";
                    container rib-in-pre {
                        config false;
                        description
                          "Container for the pre-import-policy version of BGP routes learned from BGP neighbors.";
                        list routes {
                            config false;
                            key "prefix neighbor";
                            description
                              "List of IPv4 routes.";
                            uses state-common-key;

                            leaf attr-id {
                                description
                                  "Leaf reference to networkinstance/protocols/bgp/rib/attr-sets/attr-set/index.";
                                type leafref {
                                    path "../../../../../srl_nokia-rib-bgp-routes:attr-sets/srl_nokia-rib-bgp-routes:attr-set/srl_nokia-rib-bgp-routes:index";
                                }
                            }
                        }
                    }
                    container rib-in-post {
                        config false;
                        description
                          "Container for the post-import-policy version of BGP routes learned from BGP neighbors.";
                        list routes {
                            config false;
                            description
                              "List of IPv4 routes";
                            key  "prefix neighbor";
                            uses state-common-key;
                            uses state-routes-common;
                            leaf attr-id {
                                description
                                  "Leaf reference to networkinstance/protocols/bgp/rib/attr-sets/attr-set/index.";
                                type leafref {
                                    path "../../../../../srl_nokia-rib-bgp-routes:attr-sets/srl_nokia-rib-bgp-routes:attr-set/srl_nokia-rib-bgp-routes:index";
                                }
                            }
                        }
                    }

                    container rib-out-post {
                        config false;
                        description
                          "Container for the post-export-policy version of BGP routes advertised to BGP neighbors.";
                        list routes {
                            config false;
                            key "prefix neighbor";
                            description
                              "List of IPv4 routes.";
                            uses state-common-key;
                            leaf attr-id {
                                description
                                  "Leaf reference to networkinstance/protocols/bgp/rib/attr-sets/attr-set/index.";
                                type leafref {
                                    path "../../../../../srl_nokia-rib-bgp-routes:attr-sets/srl_nokia-rib-bgp-routes:attr-set/srl_nokia-rib-bgp-routes:index";
                                }
                            }
                        }
                    }
                }
            }
            container ipv6-unicast {
                config false;
                description
                  "Container for RIB state of IPv6-unicast routes.";
                container local-rib {
                    config false;
                    description
                      "Container for local RIB, containing all imported routes from other protocols plus the post-import-policy version of all IPv6 routes learned from all BGP neighbors.";
                    list routes {
                        config false;
                        key "prefix neighbor origin-protocol";
                        description
                          "List of IPv6 routes in the local RIB.";
                        uses state-common-key;
                        leaf origin-protocol {
                            description
                                "If the route was imported from another protocol, this is the protocol name.";
                            type enumeration {
                                enum "static" {}
                                enum "aggregate" {}
                                enum "direct" {}
                                enum "bgp" {}
                                enum "host" {}
                                enum "isis" {}
                                enum "ospfv2" {}
                                enum "ospfv3" {}
                                enum "local" {}
                                enum "sdk" {}
                            }
                        }
                        uses state-routes-common;
                        leaf attr-id {
                            description
                              "Leaf reference to networkinstance/protocols/bgp/rib/attr-sets/attr-set/index";
                            type leafref {
                                path "../../../../srl_nokia-rib-bgp-routes:attr-sets/srl_nokia-rib-bgp-routes:attr-set/srl_nokia-rib-bgp-routes:index";
                            }
                        }
                    }
                }

                container rib-in-out {
                    config false;
                    description
                      "Container for BGP routes learned and advertised to BGP neighbors.";
                    container rib-in-pre {
                        config false;
                        description
                          "Container for the pre-import-policy version of BGP routes learned from BGP neighbors.";
                        list routes {
                            config false;
                            key "prefix neighbor";
                            description
                              "List of IPv6 routes.";
                            uses state-common-key;
                            leaf attr-id {
                                description
                                  "Leaf reference to networkinstance/protocols/bgp/rib/attr-sets/attr-set/index.";
                                type leafref {
                                    path "../../../../../srl_nokia-rib-bgp-routes:attr-sets/srl_nokia-rib-bgp-routes:attr-set/srl_nokia-rib-bgp-routes:index";
                                }
                            }
                        }
                    }
                    container rib-in-post {
                        config false;
                        description
                          "Container for the post-import-policy version of BGP routes learned from BGP neighbors.";
                        list routes {
                            config false;
                            description
                              "List of IPv6 routes";
                            key  "prefix neighbor";
                            uses state-common-key;
                            uses state-routes-common;
                            leaf attr-id {
                                description
                                  "Leaf reference to networkinstance/protocols/bgp/rib/attr-sets/attr-set/index.";
                                type leafref {
                                    path "../../../../../srl_nokia-rib-bgp-routes:attr-sets/srl_nokia-rib-bgp-routes:attr-set/srl_nokia-rib-bgp-routes:index";
                                }
                            }
                        }
                    }

                    container rib-out-post {
                        config false;
                        description
                          "Container for the post-export-policy version of BGP routes advertised to BGP neighbors.";
                        list routes {
                            config false;
                            key "prefix neighbor";
                            description
                              "List of IPv6 routes.";
                            uses state-common-key;
                            leaf attr-id {
                                description
                                  "Leaf reference to networkinstance/protocols/bgp/rib/attr-sets/attr-set/index.";
                                type leafref {
                                    path "../../../../../srl_nokia-rib-bgp-routes:attr-sets/srl_nokia-rib-bgp-routes:attr-set/srl_nokia-rib-bgp-routes:index";
                                }
                            }
                        }

                    }
                }
            }
            container attr-sets {
                config false;
                description
                  "Container for BGP RIB path attribute sets that can be shared by one or more BGP routes.";
                list attr-set {
                    config false;
                    description
                      "List of attribute sets.";
                    key "attr-set-type index";
                    leaf attr-set-type {
                        description "The type of the attribute-set. RIB-IN attribute sets can only be referenced by
                            BGP routes in the RIB-IN. RIB-OUT attribute sets can only be referenced by
                            BGP routes in the RIB-OUT.";
                        type enumeration {
                            enum rib-in {value 1;}
                            enum rib-out {value 2;}
                        }
                    }
                    leaf index {
                        description
                          "A unique internal identifier of the attribute set.";
                        type uint64;
                    }
                    container as-path {
                        config false;
                        description 
                          "A container for the AS path attribute of the attribute set.";

                        list segment {
                            config false;
                            description 
                              "A list of segments. Each segment has a type and a list of one or more AS
                                numbers.";
                            key "as-path-index";
                            leaf as-path-index {
                                config false;
                                description
                                  "RIB attribute AS Path index";
                                type uint32;
                            }

                            leaf type {
                                description
                                  "The type of the AS path segment.";
                                type enumeration {
                                    enum as-set {}
                                    enum as-sequence {}
                                    enum as-confed-sequence {}
                                    enum as-confed-set {}
                                }
                            }
                            leaf-list member {
                                description
                                  "A list of AS numbers (each of which is a 2byte-ASN or a 4byte-ASN) that belong to the AS path segment.";
                                type uint32 {
                                    range "1..4294967295";
                                }
                                ordered-by user;
                            }
                        }
                    }
                    leaf origin {
                        description
                          "The value of the ORIGIN path attribute";
                        type enumeration {
                            enum igp {}
                            enum egp {}
                            enum incomplete {}
                        }
                    }
                    leaf atomic-aggregate {
                        description
                          "Set to true to indicate the presence of the ATOMIC_AGGREGATE path attribute.";
                        type boolean;
                    }
                    leaf next-hop {
                        description "The IPv4 or IPv6 address of the BGP next-hop (extracted from the
                            NEXT_HOP field of the UPDATE or the MP_REACH_NLRI next-hop).";
                        type srl_nokia-comm:ip-address-with-zone;
                    }
                    leaf med {
                        description
                          "The value of the MULTI_EXIT_DISC path attribute.";
                        type uint32;
                    }
                    leaf local-pref {
                        description
                          "The value of the LOCAL_PREF path attribute.";
                        type uint32;
                    }
                    leaf originator-id {
                        description "The address in the ORIGINATOR_ID attribute added by a route reflector.";
                        type srl_nokia-comm:ip-address;
                    }
                    leaf-list cluster-list {
                        description "The list of IPv4 addresses in the CLUSTER_LIST path attribute.";
                        type srl_nokia-comm:ip-address;
                        ordered-by user;
                    }
                    leaf aigp {
                        description
                          "The value in the AIGP path attribute.";
                        type uint64;
                    }
                    container aggregator {
                        config false;
                        description
                          "The identification of the router that performed aggregation to create and advertise the route";

                        leaf as-number {
                            description
                              "The 2byte or 4byte AS number of the router that formed the aggregate route.";
                            type uint32 {
                                range "1..4294967295";
                            }
                        }
                        leaf address {
                            description "The router ID of the BGP router that formed the aggregate route.";
                            type srl_nokia-comm:ip-address;
                        }
                    }

                    container communities {
                        config false;
                        description
                          "Container for different types of BGP communities";

                        leaf-list community {
                            description
                              "List of standard 4-byte community values in the COMMUNITY path attribute. Each should be displayed in the format <0..65355>:<0..65535>";
                            type string;
                            ordered-by user;
                        }
                        leaf-list ext-community {
                            description "List of extended 8-byte community values in the COMMUNITY path
                                attribute.";
                            type string;
                            ordered-by user;
                        }
                        leaf-list large-community {
                            description 
                              "List of large 12-byte community values in the LARGE_COMMUNITY path
                              attribute. Each should be displayed in the format: <0..4294967295>:<0..4294967295>:<
                              0..4294967295>";
                            type string {
                                length 1..72;
                            }
                            ordered-by user;
                        }
                    }

                    container unknown-attributes {
                        config false;
                        description
                          "Container for unknown path attributes";

                        list unknown-attribute {
                            config false;
                            description
                              "List of unknown BGP path attributes";
                            key "unknown-attr-index";

                            leaf unknown-attr-index {
                                config false;
                                description
                                  "The unknown path attribute index";
                                type uint32;
                            }

                            leaf attr-type {
                                config false;
                                description
                                  "The type code of the unknown path attribute";
                                type uint8;
                            }
                            leaf attr-len {
                                config false;
                                description
                                  "The length of the unknown path attribute";
                                type uint16;
                            }
                            leaf optional {
                                config false;
                                description
                                  "Set to true if the unknown path attribute has the optional flag is set to 1.";
                                type boolean;
                            }
                            leaf transitive {
                                config false;
                                description
                                  "Set to true if the unknown path attribute has the transitive flag is set to 1.";
                                type boolean;
                            }
                            leaf partial {
                                description
                                  "Set to true if the unknown path attribute has the partial flag is set to 1.";
                                type boolean;
                            }
                            leaf extended {
                                description
                                  "Set to true if the unknown path attribute has the extended length flag is set to 1.";
                                type boolean;
                            }
                        }
                    }
                }
            }
        }
    }
    augment "/srl_nokia-netinst:network-instance" {
        uses bgp-rib-top;
    }
}
